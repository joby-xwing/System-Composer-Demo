# Requirement_Set_test
Tesing how the requirement functionality works

## XW_Power_1: The ECBU SHALL distribute electrical power to individual component loads.. Change (Functional)

## #2: Electrical components SHALL be propoerly grounded (Functional)

### #4: Electrical components SHALL have a resistance from connector to ground of not less than 5mA (Functional)

## #3: There SHALL be a means of controlling the ECBU status (Functional)

## #6 (Functional)
Th

## #7: Their shall be a means to monitor the electrical system (Functional)
